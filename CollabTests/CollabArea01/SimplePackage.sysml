package SimplePackage {

//  TODO The following line does not work in Eclipse
//  with the SubfolderPackage.sysml not being in the same directory;
//  Are there available Eclipse project settings to allow packages
//  to be in other directories?
//    
//    import SubfolderPackage::*; 

    part <sp1> simplePart01;
}
